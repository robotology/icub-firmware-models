# control

## #1: compute minimum jerk position traj (Functional)

## #2: Compute PID control according to position error (Functional)

## #3: Accept targets from many sources (Functional)

## #4: Send data to cm7 via CAN or ICC (Functional)
