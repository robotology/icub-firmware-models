# functional

## #1: Accept position setpoint for min jerk (Functional)

## #2: Read different types of joint encoders (Functional)

## #3: Calibrate a joint according to type (Functional)

## #4: Compute PID control according to position error (Functional)
